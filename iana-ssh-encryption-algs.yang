module iana-ssh-encryption-algs {
  yang-version 1.1;
  namespace "urn:ietf:params:xml:ns:yang:iana-ssh-encryption-algs";
  prefix sshea;

  organization
    "Internet Assigned Numbers Authority (IANA)";

  contact
    "Postal: ICANN
             12025 Waterfront Drive, Suite 300
             Los Angeles, CA  90094-2536
             United States of America
     Tel:    +1 310 301 5800
     Email:  iana@iana.org";

  description
    "This module defines enumerations for the encryption algorithms
     defined in the 'Encryption Algorithm Names' sub-registry of the
     'Secure Shell (SSH) Protocol Parameters' registry maintained
     by IANA.

     Copyright (c) 2024 IETF Trust and the persons identified as
     authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     The initial version of this YANG module is part of RFC EEEE
     (https://www.rfc-editor.org/info/rfcEEEE); see the RFC
     itself for full legal notices.

     All versions of this module are published by IANA at
     https://www.iana.org/assignments/yang-parameters.";

  revision 2024-03-16 {
    description
      "This initial version of the module was created using
       the script defined in RFC EEEE to reflect the contents
       of the encryption algorithms registry maintained by IANA.";
    reference
      "RFC EEEE: YANG Groupings for SSH Clients and SSH Servers";
  }

  typedef ssh-encryption-algorithm {
    type enumeration {

      enum 3des-cbc {
        description
          "Enumeration for the '3des-cbc' algorithm. Section 6.3";
        reference
          "RFC 4253:
             The Secure Shell (SSH) Transport Layer Protocol";
      }

      enum blowfish-cbc {
        description
          "Enumeration for the 'blowfish-cbc' algorithm. Section
           6.3";
        reference
          "RFC 4253:
             The Secure Shell (SSH) Transport Layer Protocol";
      }

      enum twofish256-cbc {
        description
          "Enumeration for the 'twofish256-cbc' algorithm. Section
           6.3";
        reference
          "RFC 4253:
             The Secure Shell (SSH) Transport Layer Protocol";
      }

      enum twofish-cbc {
        description
          "Enumeration for the 'twofish-cbc' algorithm. Section 6.3";
        reference
          "RFC 4253:
             The Secure Shell (SSH) Transport Layer Protocol";
      }

      enum twofish192-cbc {
        description
          "Enumeration for the 'twofish192-cbc' algorithm. Section
           6.3";
        reference
          "RFC 4253:
             The Secure Shell (SSH) Transport Layer Protocol";
      }

      enum twofish128-cbc {
        description
          "Enumeration for the 'twofish128-cbc' algorithm. Section
           6.3";
        reference
          "RFC 4253:
             The Secure Shell (SSH) Transport Layer Protocol";
      }

      enum aes256-cbc {
        description
          "Enumeration for the 'aes256-cbc' algorithm. Section 6.3";
        reference
          "RFC 4253:
             The Secure Shell (SSH) Transport Layer Protocol";
      }

      enum aes192-cbc {
        description
          "Enumeration for the 'aes192-cbc' algorithm. Section 6.3";
        reference
          "RFC 4253:
             The Secure Shell (SSH) Transport Layer Protocol";
      }

      enum aes128-cbc {
        description
          "Enumeration for the 'aes128-cbc' algorithm. Section 6.3";
        reference
          "RFC 4253:
             The Secure Shell (SSH) Transport Layer Protocol";
      }

      enum serpent256-cbc {
        description
          "Enumeration for the 'serpent256-cbc' algorithm. Section
           6.3";
        reference
          "RFC 4253:
             The Secure Shell (SSH) Transport Layer Protocol";
      }

      enum serpent192-cbc {
        description
          "Enumeration for the 'serpent192-cbc' algorithm. Section
           6.3";
        reference
          "RFC 4253:
             The Secure Shell (SSH) Transport Layer Protocol";
      }

      enum serpent128-cbc {
        description
          "Enumeration for the 'serpent128-cbc' algorithm. Section
           6.3";
        reference
          "RFC 4253:
             The Secure Shell (SSH) Transport Layer Protocol";
      }

      enum arcfour {
        status obsolete;
        description
          "Enumeration for the 'arcfour' algorithm.";
        reference
          "RFC 8758:
             Deprecating RC4 in Secure Shell (SSH)";
      }

      enum idea-cbc {
        description
          "Enumeration for the 'idea-cbc' algorithm. Section 6.3";
        reference
          "RFC 4253:
             The Secure Shell (SSH) Transport Layer Protocol";
      }

      enum cast128-cbc {
        description
          "Enumeration for the 'cast128-cbc' algorithm. Section 6.3";
        reference
          "RFC 4253:
             The Secure Shell (SSH) Transport Layer Protocol";
      }

      enum none {
        description
          "Enumeration for the 'none' algorithm. Section 6.3";
        reference
          "RFC 4253:
             The Secure Shell (SSH) Transport Layer Protocol";
      }

      enum des-cbc {
        status obsolete;
        description
          "Enumeration for the 'des-cbc' algorithm.";
        reference
          "FIPS-46-3:
             Data Encryption Standard (DES)";
      }

      enum arcfour128 {
        status obsolete;
        description
          "Enumeration for the 'arcfour128' algorithm.";
        reference
          "RFC 8758:
             Deprecating RC4 in Secure Shell (SSH)";
      }

      enum arcfour256 {
        status obsolete;
        description
          "Enumeration for the 'arcfour256' algorithm.";
        reference
          "RFC 8758:
             Deprecating RC4 in Secure Shell (SSH)";
      }

      enum aes128-ctr {
        description
          "Enumeration for the 'aes128-ctr' algorithm.";
        reference
          "RFC 4344:
             The Secure Shell (SSH) Transport Layer Encryption
             Modes";
      }

      enum aes192-ctr {
        description
          "Enumeration for the 'aes192-ctr' algorithm.";
        reference
          "RFC 4344:
             The Secure Shell (SSH) Transport Layer Encryption
             Modes";
      }

      enum aes256-ctr {
        description
          "Enumeration for the 'aes256-ctr' algorithm.";
        reference
          "RFC 4344:
             The Secure Shell (SSH) Transport Layer Encryption
             Modes";
      }

      enum 3des-ctr {
        description
          "Enumeration for the '3des-ctr' algorithm.";
        reference
          "RFC 4344:
             The Secure Shell (SSH) Transport Layer Encryption
             Modes";
      }

      enum blowfish-ctr {
        description
          "Enumeration for the 'blowfish-ctr' algorithm.";
        reference
          "RFC 4344:
             The Secure Shell (SSH) Transport Layer Encryption
             Modes";
      }

      enum twofish128-ctr {
        description
          "Enumeration for the 'twofish128-ctr' algorithm.";
        reference
          "RFC 4344:
             The Secure Shell (SSH) Transport Layer Encryption
             Modes";
      }

      enum twofish192-ctr {
        description
          "Enumeration for the 'twofish192-ctr' algorithm.";
        reference
          "RFC 4344:
             The Secure Shell (SSH) Transport Layer Encryption
             Modes";
      }

      enum twofish256-ctr {
        description
          "Enumeration for the 'twofish256-ctr' algorithm.";
        reference
          "RFC 4344:
             The Secure Shell (SSH) Transport Layer Encryption
             Modes";
      }

      enum serpent128-ctr {
        description
          "Enumeration for the 'serpent128-ctr' algorithm.";
        reference
          "RFC 4344:
             The Secure Shell (SSH) Transport Layer Encryption
             Modes";
      }

      enum serpent192-ctr {
        description
          "Enumeration for the 'serpent192-ctr' algorithm.";
        reference
          "RFC 4344:
             The Secure Shell (SSH) Transport Layer Encryption
             Modes";
      }

      enum serpent256-ctr {
        description
          "Enumeration for the 'serpent256-ctr' algorithm.";
        reference
          "RFC 4344:
             The Secure Shell (SSH) Transport Layer Encryption
             Modes";
      }

      enum idea-ctr {
        description
          "Enumeration for the 'idea-ctr' algorithm.";
        reference
          "RFC 4344:
             The Secure Shell (SSH) Transport Layer Encryption
             Modes";
      }

      enum cast128-ctr {
        description
          "Enumeration for the 'cast128-ctr' algorithm.";
        reference
          "RFC 4344:
             The Secure Shell (SSH) Transport Layer Encryption
             Modes";
      }

      enum AEAD_AES_128_GCM {
        description
          "Enumeration for the 'AEAD_AES_128_GCM' algorithm. Section
           6.1";
        reference
          "RFC 5647:
             AES Galois Counter Mode for the Secure Shell Transport
             Layer Protocol";
      }

      enum AEAD_AES_256_GCM {
        description
          "Enumeration for the 'AEAD_AES_256_GCM' algorithm. Section
           6.2";
        reference
          "RFC 5647:
             AES Galois Counter Mode for the Secure Shell Transport
             Layer Protocol";
      }
    }
    description
      "An enumeration for SSH encryption algorithms.";
  }

}
