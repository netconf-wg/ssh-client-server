module iana-ssh-mac-algs {
  yang-version 1.1;
  namespace "urn:ietf:params:xml:ns:yang:iana-ssh-mac-algs";
  prefix sshma;

  organization
    "Internet Assigned Numbers Authority (IANA)";

  contact
    "Postal: ICANN
             12025 Waterfront Drive, Suite 300
             Los Angeles, CA  90094-2536
             United States of America
     Tel:    +1 310 301 5800
     Email:  iana@iana.org";

  description
    "This module defines enumerations for the MAC algorithms
     defined in the 'MAC Algorithm Names' sub-registry of the
     'Secure Shell (SSH) Protocol Parameters' registry maintained
     by IANA.

     Copyright (c) 2024 IETF Trust and the persons identified as
     authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     The initial version of this YANG module is part of RFC EEEE
     (https://www.rfc-editor.org/info/rfcEEEE); see the RFC
     itself for full legal notices.

     All versions of this module are published by IANA at
     https://www.iana.org/assignments/yang-parameters.";

  revision 2024-03-16 {
    description
      "This initial version of the module was created using
       the script defined in RFC EEEE to reflect the contents
       of the mac algorithms registry maintained by IANA.";
    reference
      "RFC EEEE: YANG Groupings for SSH Clients and SSH Servers";
  }

  typedef ssh-mac-algorithm {
    type enumeration {

      enum hmac-sha1 {
        description
          "Enumeration for the 'hmac-sha1' algorithm. Section 6.4";
        reference
          "RFC 4253:
             The Secure Shell (SSH) Transport Layer Protocol";
      }

      enum hmac-sha1-96 {
        description
          "Enumeration for the 'hmac-sha1-96' algorithm. Section
           6.4";
        reference
          "RFC 4253:
             The Secure Shell (SSH) Transport Layer Protocol";
      }

      enum hmac-md5 {
        description
          "Enumeration for the 'hmac-md5' algorithm. Section 6.4";
        reference
          "RFC 4253:
             The Secure Shell (SSH) Transport Layer Protocol";
      }

      enum hmac-md5-96 {
        description
          "Enumeration for the 'hmac-md5-96' algorithm. Section 6.4";
        reference
          "RFC 4253:
             The Secure Shell (SSH) Transport Layer Protocol";
      }

      enum none {
        description
          "Enumeration for the 'none' algorithm. Section 6.4";
        reference
          "RFC 4253:
             The Secure Shell (SSH) Transport Layer Protocol";
      }

      enum AEAD_AES_128_GCM {
        description
          "Enumeration for the 'AEAD_AES_128_GCM' algorithm. Section
           6.1";
        reference
          "RFC 5647:
             AES Galois Counter Mode for the Secure Shell Transport
             Layer Protocol";
      }

      enum AEAD_AES_256_GCM {
        description
          "Enumeration for the 'AEAD_AES_256_GCM' algorithm. Section
           6.2";
        reference
          "RFC 5647:
             AES Galois Counter Mode for the Secure Shell Transport
             Layer Protocol";
      }

      enum hmac-sha2-256 {
        description
          "Enumeration for the 'hmac-sha2-256' algorithm. Section 2";
        reference
          "RFC 6668:
             SHA-2 Data Integrity Verification for the Secure Shell
             (SSH) Transport Layer Protocol";
      }

      enum hmac-sha2-512 {
        description
          "Enumeration for the 'hmac-sha2-512' algorithm. Section 2";
        reference
          "RFC 6668:
             SHA-2 Data Integrity Verification for the Secure Shell
             (SSH) Transport Layer Protocol";
      }
    }
    description
      "An enumeration for SSH mac algorithms.";
  }

}
